# Aircraft Propulsion Subsystem Requirements

# Specification: Propulsion Requirements

## SO-PROP-001
- Requirement Text: The propulsion assembly shall provide minimum 200 kN total thrust.
- Rationale: Derived from performance specification PS-2026-03, section 4.2
- Verification Method: Analysis and Test
- Priority: Critical
- Status: Approved

## SO-PROP-002
- Requirement Text: Fuel system shall maintain supply to all engines after single tank breach.
- Rationale: Safety requirement per FAR 25.963
- Verification Method: Test
- Priority: Critical
- Status: Approved

## SO-PROP-003
- Requirement Text: Engine control unit software shall be DO-178C DAL B compliant.
- Rationale: Certification baseline requirement
- Verification Method: Inspection
- Priority: Critical
- Status: Approved

## SO-PROP-004
- Requirement Text: Propeller diameter shall not exceed 2.5 m for ground clearance.
- Rationale: Airport compatibility constraint
- Verification Method: Analysis
- Priority: High
- Status: Approved

## SO-PROP-005
- Requirement Text: Mean time to failure shall exceed 40000 flight hours.
- Rationale: Reliability target from operator agreement
- Verification Method: Analysis and Test
- Priority: Critical
- Status: Approved

## SO-PROP-006
- Requirement Text: Specific fuel consumption shall not exceed 0.020 g/kN/s at cruise.
- Rationale: Fuel efficiency target
- Verification Method: Test
- Priority: High
- Status: Draft
- Derives From -> SO-PROP-001
